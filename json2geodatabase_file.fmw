FME workspace json2geodatabase_file.fmw

Parameters:
- DestDataset_GEODATABASE_FILE =
- SourceDataset_JSON =

Readers:
- JSON_1: JSON from $(SourceDataset_JSON)

Writers:
- GEODATABASE_FILE_1: GEODATABASE_FILE to $(DestDataset_GEODATABASE_FILE)

Note: How To: Convert a JSON URL to a feature class using the Data Interoperability extension / https://support.esri.com/en/technical-article/000019108
VertexCreator
    MEASURE_TYPE = Continuous
    MISSING_VAL_MODE = Compute
    MODE_NAME = Add Point
    XVAL = @Value(results{0}.geometry.location.lng)
    YVAL = @Value(results{0}.geometry.location.lat)
    -> CoordinateSystemSetter
CoordinateSystemSetter
    COORDSYS = EPSG4326
    -> AttributeCreator
AttributeCreator
    ATTR_TABLE:
      SET_TO results{}.geometry.location.lat = results{}.geometry.location.lat
      SET_TO results{}.geometry.location.lng = results{}.geometry.location.lng
      SET_TO results{}.name = results{}.name
      SET_TO results{}.vicinity = results{}.vicinity
    -> JSONFeature (writer GEODATABASE_FILE_1)

Bookmark: Reader Feature Types
JSONFeature (reader JSON_1)
    attributes: next_page_token string, results{}.price_level int, results{}.opening_hours.open_now boolean, results{}.business_status string, results{}.geometry.location.lat float, results{}.geometry.location.lng float, results{}.geometry.viewport.northeast.lat float, results{}.geometry.viewport.northeast.lng float, results{}.geometry.viewport.southwest.lat float, results{}.geometry.viewport.southwest.lng float, results{}.icon string, results{}.icon_background_color string, results{}.icon_mask_base_uri string, results{}.name string, results{}.permanently_closed boolean, results{}.photos{}.height int, results{}.photos{}.html_attributions{} string, results{}.photos{}.photo_reference string, results{}.photos{}.width int, results{}.place_id string, results{}.plus_code.compound_code string, results{}.plus_code.global_code string, results{}.rating float, results{}.reference string, results{}.scope string, results{}.types{} string, results{}.user_ratings_total int, results{}.vicinity string, status string
    -> VertexCreator

Bookmark: Writer Feature Types
JSONFeature (writer GEODATABASE_FILE_1)
    attributes: next_page_token char(2048), results___price_level char(20), results___opening_hours_open_now boolean, results___business_status char(2048), results___geometry_location_lat double, results___geometry_location_lng double, results___geometry_viewport_northeast_lat double, results___geometry_viewport_northeast_lng double, results___geometry_viewport_southwest_lat double, results___geometry_viewport_southwest_lng double, results___icon char(2048), results___icon_background_color char(2048), results___icon_mask_base_uri char(2048), results___name char(2048), results___permanently_closed boolean, results___photos___height char(20), results___photos___html_attributions__ char(2048), results___photos___photo_reference char(2048), results___photos___width char(20), results___place_id char(2048), results___plus_code_compound_code char(2048), results___plus_code_global_code char(2048), results___rating double, results___reference char(2048), results___scope char(2048), results___types__ char(2048), results___user_ratings_total char(20), results___vicinity char(2048), status char(2048)
