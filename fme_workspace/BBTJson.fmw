FME workspace BBTJson.fmw
Title: JSON to NONE

Parameters:
- DestDataset_SHAPEFILE =
- DestDataset_SHAPEFILE_3 =
- SourceDataset_JSON =

Readers:
- JSON_1: JSON from $(SourceDataset_JSON)

Writers:
- SHAPEFILE_1: SHAPEFILE to $(DestDataset_SHAPEFILE)
- SHAPEFILE_2: SHAPEFILE to $(DestDataset_SHAPEFILE_3)

JSONFeature (reader JSON_1)
    attributes: name string, lat float, lng float, place_id string, address string
Creator
    GEOMTYPE = Geometry Object
    NUM = 1
    CREATED -> HTTPCaller
HTTPCaller
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = https://maps.googleapis.com/maps/api/place/nearbysearch/json?location=43.91407265468856%2C-79.44731313715351&radius=10000&keyword=bubbletea&key=AIzaSyBnui5g3BeTm3LcbBLBvbLrWFcwMEv6J8k
    TRANSFER_TIMEOUT_LENGTH = 90
    USE_COOKIES = No
    VERIFY_SSL_CERTIFICATES = Yes
    -> JSONFragmenter
Note: Rename vicinity to address
AttributeManager
    ATTR_TABLE = RENAME_SET_VALUE vicinity > address
    -> GoogleAPIbbt (writer SHAPEFILE_2)
GoogleAPIbbt (writer SHAPEFILE_2)
    attributes: name varchar(254), lat double, lng double, place_id varchar(254), address varchar(254)
VertexCreator
    INDEX = 0
    MEASURE_TYPE = Continuous
    MISSING_VAL_MODE = Compute
    MODE_NAME = Add Point
CoordinateSystemSetter
    COORDSYS = LL84
    -> BBT (writer SHAPEFILE_1)
BBT (writer SHAPEFILE_1)
    attributes: name varchar(254), lat double, lng double, place_id varchar(254), address varchar(254)

Bookmark: Extract Attributes
JSONFragmenter
    EXPLODE_FORMAT = JSON
    EXTRACT_ATTR = Yes
    JSON_ATTR = _response_body
    JSON_QUERY = json["results"][*]
    NEW_ATTRIBUTES = geometry name place_id vicinity
    READ_FROM_FILE = NO
    RECURSIVE = No
    REJECT_EMPTY_LISTS = YES
    FRAGMENTS -> JSONFragmenter_2
JSONFragmenter_2
    EXPLODE_FORMAT = JSON
    EXTRACT_ATTR = Yes
    JSON_ATTR = geometry
    JSON_QUERY = json["location"]
    NEW_ATTRIBUTES = lat lng
    READ_FROM_FILE = NO
    RECURSIVE = No
    REJECT_EMPTY_LISTS = YES
    FRAGMENTS -> VertexCreator_2
VertexCreator_2
    MEASURE_TYPE = Continuous
    MISSING_VAL_MODE = Compute
    MODE_NAME = Add Point
    XVAL = @Value(lng)
    YVAL = @Value(lat)
    -> CoordinateSystemSetter_2
CoordinateSystemSetter_2
    COORDSYS = LL84
    -> AttributeManager
